# staqueholder

## ST01: Endurance (Informational)
The system shall operate at least 20 mins.

## ST02: Task (Informational)
The system shall cover the surroundings of a building.

## #3: Capabilities (Container)

### ST04: Altitude (Informational)
The system shall estimate its altitude to monitor its operation.

### ST05: Position (Informational)
The system shall estimate its position to monitor its operation.

### ST06: Velocity (Informational)
The system shall estimate its position to monitor its operation.

## #7: Reliability (Container)

### ST07: MTBR (Functional)
The system shall have a Mean Time Before Repair of 1 month.

### ST08: MTBF (Functional)
The system shall have a Mean Time Before Failure of 1 year.
