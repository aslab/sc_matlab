# system

## #1: Endurance (Container)

### SYS01: BatteryCapacity (Functional)
The system shall have a battery capacity sufficient for 20 mins of continous operation and a weigh less than 0.5 kg.

### SYS02: BatteryCharging (Functional)
The system shall be able to charge in maximum 2h.

### SYS03: MotorDistribution (Functional)
The system shall be a quadcopter.

## #6: Autonomy (Container)

### SYS04: Localization (Functional)
The system shall be able to determinate its current position within 0.3 m.

### SYS05: PathGeneration (Functional)
The system shall automatically generate a path from its current position to a newly specified position.

### SYS06: PathFollowing (Functional)
The system shall follow a generated path with a maximum deviation of +/- 0.3 m.

### SYS07: CollisionAvoidance (Functional)
The system shall avoid collision during its operation.

## #11: LifeExpectancy (Container)

### SYS08: BatteryLife (Functional)
The system battery shall be able to operate without failing for 1 year.

### SYS09: SensorLife (Functional)
The system sensors shall be able to operate without failing for 1 year.

### SYS10: MechanicalLife (Functional)
The system mechanical components shall be able to operate without failing for 1 year.
