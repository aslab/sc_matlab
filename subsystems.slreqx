# subsystems

## #1: Battery (Container)

### BAT01: BatteryCapacity (Functional)
The battery shall have a capacity of 2.5 kWh.

### BAT02: Battery Charging (Functional)
The battery charging station shall have a minimum charging current of 2 amperes.

## #4: Structure (Container)

### ST01: Support (Functional)
The structure shall support a maximum weight of 320 g.

## #6: Propulsion (Container)

### PR01: MotorPower (Functional)
The motors shall have a maximum power output of at least 50 W.

### PR02: MotorSpeed (Functional)
The motos shall have a top speed of at least 200 rpm.

## #9: Control (Container)

### CONT01: AltitudeEstimation (Functional)
The system shall use an IMU, a camera, a sonar and a filter to estimate the altitude with an accuracy of +/- 0.15 m.

### CONT02: PositionEstimation (Functional)
The system shall use an IMU and a camera and a Kalman filter to estimate the position with an accuracy of +/- 0.15 m.

### CONT03: VelocityEstimation (Functional)
The system shall use an IMU and a camera and a Kalman filter to estimate the velocity.

### CONT04: PositionControl (Functional)
The position of the drone shall have at least a PD controller.

### CONT05: ControllerRate (Functional)
The controller shall operate at a frequency of 2 GHz.

## #15: PathGeneration (Container)

### PG01: PathAlgorithm (Functional)
The path generation function shall create a path for the drone starting from the end position and working backwards to the drone's current position.

### PG02: ReplanningPath (Functional)
The path generation function shall automatically generate a new path when the current path will result in an object collision.

## #18: ComponentLife (Functional)

### CL01: CameraLife (Functional)
The camera shall have a minimum life expectancy of 73 hours.

### CL02: IMULife (Functional)
The IMU shall have a minimum life expectancy of 73 hours.

### CL03: SonarLife (Functional)
The sonar shall have a minimum life expectancy of 73 hours.

### CL04: MotorLife (Functional)
The motor shall have a minimum life expectancy of 2000 cycles.

### CL05: BatteryLife (Functional)
The battery shall be able to withstand 1460 full charge/discharge cycles before needing to be replaced.

### CL06: ElectronicsLife (Functional)
The camera shall have a minimum life expectancy of 73 hours.

### CL07: PropellersLife (Functional)
The propellers shall have a minimum life expectancy of 30 take-off/landinglandings cicles.
